module vxlanTenant {

  namespace "http://example.com/vxlanTenant";
  prefix vxlanTenant;

  import ietf-inet-types {
    prefix inet;
  }
  import tailf-common {
    prefix tailf;
  }
  import tailf-ncs {
    prefix ncs;
  }

  description
    "Bla bla...";

  revision 2016-01-01 {
    description
      "Initial revision.";
  }

  typedef ipv4-network {
    type string {
      pattern
        '(([0-9]|[1-9][0-9]|1[0-9][0-9]|2[0-4][0-9]|25[0-5])\.){3}'
        +  '([0-9]|[1-9][0-9]|1[0-9][0-9]|2[0-4][0-9]|25[0-5])'
        + '/(([0-9])|([1-2][0-9])|(3[0-2]))';
    }
  }

  list vxlanTenant {
    description "This is an RFS skeleton service";

    key name;
    leaf name {
      tailf:info "Unique Tenant id; ex) ACME";
      tailf:cli-allow-range;
      type string;
    }

    uses ncs:service-data;
    ncs:servicepoint vxlanTenant-servicepoint;

    leaf asn {
      mandatory true;
      tailf:info "ASN; ex) 65002";
      type uint32;
    }

    leaf vnid-prefix {
      tailf:info "VNID prefix(4 digits)  +VLAN-ID; ex) 1000";
      type uint32 {
        range "50..9999";
      }
      default 1000;
    }

    leaf l3-vlanid {
      mandatory true;
      tailf:info "L3 VLAN-ID , ex) 999";
      type uint32 {
        range "4..4095";
      }
    }

    list l2-vni {
      key vlan-id;
      leaf vlan-id {
        tailf:info "L2 VLAN-ID, will be used to mcast group IP as well, ex) 201";
        type uint32 {
          range "4..254";
        }
      }

      leaf svi-ipaddr {
        mandatory true;
        type ipv4-network;
      }
    }    

    list vtep {
      key switch;
      leaf switch {
        tailf:info "vtep device";
        type leafref {
          path "/ncs:devices/ncs:device/ncs:name";
        }
      }

      leaf type {
        mandatory true;
        tailf:info "type of vtep: leaf or border leaf";
        type enumeration {
          enum leaf {
            tailf:info "leaf switch - l2/l3 vni";
            value 1;
          }
          enum border {
            tailf:info "border leaf switch - l3 vni";
            value 2;
          }
        }
      }

      list access-port {
        when "../type = 'leaf'";
        key port;
        leaf port {
          mandatory true;
          tailf:info "port name of leaf switch for the Tenant; ex) 1/1";
          type string;
        }
        leaf vlan-id {
          mandatory true;
          tailf:info "vlan id of this port; ex) 201";
          type leafref {
            path "../../../l2-vni/vlan-id";
          }
        }
      }
    }
  }
}
