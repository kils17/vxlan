module tailf-ned-cisco-nx-id {
  // Generated by yanger -t ncs
  tailf:mount-id "cisco-nx-cli-5.22:cisco-nx-cli-5.22";
  tailf:ncs-device-type "cli-ned";

  namespace "http://tail-f.com/ned/cisco-nx-id";
  prefix cisco-nx-id;

  import tailf-ncs-ned {
    prefix ned;
  }
  import tailf-common {
    prefix tailf;
  }
  import tailf-ncs {
    prefix ncs;
  }

  identity cisco-nx {
    base ned:cli-ned-id;
  }
}
