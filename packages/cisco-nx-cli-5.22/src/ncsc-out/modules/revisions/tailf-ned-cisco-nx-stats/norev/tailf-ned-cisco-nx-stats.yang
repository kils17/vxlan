module tailf-ned-cisco-nx-stats {
  // Generated by yanger -t ncs
  tailf:mount-id "cisco-nx-cli-5.22:cisco-nx-cli-5.22";
  tailf:ncs-device-type "cli-ned";

  namespace "http://tail-f.com/ned/cisco-nx/stats";
  prefix nx-stats;

  import tailf-common {
    prefix tailf;
  }
  import tailf-ncs {
    prefix ncs;
  }

  grouping ncs_rpc_notif_vni-summary-grouping {
    leaf vnis {
      type string;
    }
    leaf up {
      type string;
    }
    leaf down {
      type string;
    }
  }

  grouping live_ncs_vni-summary-grouping {
    leaf vnis {
      type string;
    }
    leaf up {
      type string;
    }
    leaf down {
      type string;
    }
  }

  augment "/ncs:devices/ncs:device/ncs:live-status" {
    list inventory {
      tailf:ncs-device-type "cli-ned";
      tailf:display-when "not(../ncs:module) or ../ncs:module[ncs:name='tailf-ned-cisco-nx-stats'] or (../ncs:live-status-protocol[not(ncs:capability)]) or (../ncs:live-status-protocol/ncs:capability/ncs:module[.='tailf-ned-cisco-nx-stats'])";
      tailf:info
        "Inventory information";
      tailf:meta-data "ned-livestats:parser-info" {
        tailf:meta-value "{'show':'show inventory | xml','template':'show-inventory.xsl'}";
      }
      key "name";
      leaf name {
        type string;
      }
      leaf description {
        type string;
      }
      leaf product-id {
        type string;
      }
      leaf vendor-id {
        type string;
      }
      leaf serial {
        type string;
      }
    }
    container nve {
      tailf:ncs-device-type "cli-ned";
      tailf:display-when "not(../../ncs:module) or ../../ncs:module[ncs:name='tailf-ned-cisco-nx-stats'] or (../../ncs:live-status-protocol[not(ncs:capability)]) or (../../ncs:live-status-protocol/ncs:capability/ncs:module[.='tailf-ned-cisco-nx-stats'])";
      tailf:info
        "NVE information";
      list peers {
        tailf:meta-data "ned-livestats:parser-info" {
          tailf:meta-value "{'show':'show nve peers','template':'show_nve_peers.textfsm'}";
        }
        key "interface";
        leaf interface {
          type string;
        }
        leaf peer-ip {
          type string;
        }
        leaf state {
          type string;
        }
        leaf learntype {
          type string;
        }
        leaf uptime {
          type string;
        }
        leaf router-mac {
          type string;
        }
      }
      container vni {
        tailf:info
          "Virtual Network Identifier";
        container summary {
          tailf:meta-data "ned-livestats:parser-info" {
            tailf:meta-value "{'show':'show nve vni summary | xml','template':'show-nve-vni-summary.xsl'}";
          }
          tailf:info
            "Show vni summary";
          container control-plane {
            uses live_ncs_vni-summary-grouping;
          }
          container data-plane {
            uses live_ncs_vni-summary-grouping;
          }
          container unconfigured {
            uses live_ncs_vni-summary-grouping;
          }
        }
        list vnis {
          tailf:meta-data "ned-livestats:parser-info" {
            tailf:meta-value "{'show':'show nve vni | xml','template':'show-nve-vni.xsl'}";
          }
          key "vni";
          leaf vni {
            type string;
          }
          leaf interface {
            type string;
          }
          leaf multicast-group {
            type string;
          }
          leaf state {
            type string;
          }
          leaf mode {
            type string;
          }
          leaf type {
            type string;
          }
          leaf flags {
            type string;
          }
          container counters {
            tailf:info
              "Display vni counters";
            tailf:meta-data "ned-livestats:parser-info" {
              tailf:meta-value "{'show':'show nve vni %s counters | xml','template':'show-nve-vni-counters.xsl'}";
            }
            leaf tx-unicast-packets {
              type string;
            }
            leaf tx-unicast-bytes {
              type string;
            }
            leaf tx-multicast-packets {
              type string;
            }
            leaf tx-multicast-bytes {
              type string;
            }
            leaf rx-unicast-packets {
              type string;
            }
            leaf rx-unicast-bytes {
              type string;
            }
            leaf rx-multicast-packets {
              type string;
            }
            leaf rx-multicast-bytes {
              type string;
            }
          }
        }
      }
      list interface {
        tailf:meta-data "ned-livestats:parser-info" {
          tailf:meta-value "{'show':'show nve interface | xml','template':'show-nve-interface.xsl'}";
        }
        tailf:info
          "Interface";
        key "if-name";
        leaf if-name {
          type string;
        }
        leaf if-state {
          type string;
        }
        leaf encap-type {
          type string;
        }
        leaf vpc-capability {
          type string;
        }
        leaf host-reach-mode {
          type string;
        }
        leaf local-rmac {
          type string;
        }
        leaf source-if {
          type string;
        }
        leaf primary-ip {
          type string;
        }
        leaf secondary-ip {
          type string;
        }
      }
    }
    container mac {
      tailf:ncs-device-type "cli-ned";
      tailf:display-when "not(../../ncs:module) or ../../ncs:module[ncs:name='tailf-ned-cisco-nx-stats'] or (../../ncs:live-status-protocol[not(ncs:capability)]) or (../../ncs:live-status-protocol/ncs:capability/ncs:module[.='tailf-ned-cisco-nx-stats'])";
      tailf:info
        "MAC configuration commands";
      list address-table {
        tailf:meta-data "ned-livestats:parser-info" {
          tailf:meta-value "{'show':'show mac address-table | xml','template':'show-mac-address-table.xsl'}";
        }
        key "vlan mac-address";
        leaf vlan {
          type string;
        }
        leaf mac-address {
          type string;
        }
        leaf type {
          type string;
        }
        leaf static {
          type string;
        }
        leaf age {
          type string;
        }
        leaf secure {
          type string;
        }
        leaf ntfy {
          type string;
        }
        leaf port {
          type string;
        }
      }
    }
    container system {
      tailf:ncs-device-type "cli-ned";
      tailf:display-when "not(../../ncs:module) or ../../ncs:module[ncs:name='tailf-ned-cisco-nx-stats'] or (../../ncs:live-status-protocol[not(ncs:capability)]) or (../../ncs:live-status-protocol/ncs:capability/ncs:module[.='tailf-ned-cisco-nx-stats'])";
      tailf:info
        "System-related show commands";
      container internal {
        container l2rib {
          container event-history {
            list mac {
              tailf:meta-data "ned-livestats:parser-info" {
                tailf:meta-value "{'show':'show system internal l2rib event-history mac','template':'show_system_internal_l2rib_event-history_mac.textfsm'}";
              }
              // NCS drop tailf:cli-enforce-table
              ordered-by user;
              key "timestamp";
              leaf timestamp {
                type string;
              }
              leaf event {
                type string;
              }
            }
          }
        }
      }
    }
    container l2route {
      tailf:ncs-device-type "cli-ned";
      tailf:display-when "not(../../ncs:module) or ../../ncs:module[ncs:name='tailf-ned-cisco-nx-stats'] or (../../ncs:live-status-protocol[not(ncs:capability)]) or (../../ncs:live-status-protocol/ncs:capability/ncs:module[.='tailf-ned-cisco-nx-stats'])";
      tailf:info
        "Layer 2 routing information base";
      container evpn {
        tailf:info
          "EVPN";
        container fl {
          tailf:info
            "Flood list";
          list all {
            tailf:meta-data "ned-livestats:parser-info" {
              tailf:meta-value "{'show':'show l2route evpn fl all | xml','template':'show-l2route-evpn.xsl'}";
            }
            key "topo-id";
            leaf topo-id {
              type string;
            }
            leaf peer-id {
              type string;
            }
            leaf flood-list {
              type string;
            }
            leaf is-service-node {
              type string;
            }
          }
        }
        container imet {
          tailf:info
            "IMET Route";
          list all {
            tailf:meta-data "ned-livestats:parser-info" {
              tailf:meta-value "{'show':'show l2route evpn imet all | xml','template':'show-l2route-evpn.xsl'}";
            }
            key "topo-id";
            leaf topo-id {
              type string;
            }
            leaf vni {
              type string;
            }
            leaf prod-type {
              type string;
            }
            leaf ip-addr {
              type string;
            }
          }
        }
        container mac {
          tailf:info
            "MAC Route";
          list all {
            tailf:meta-data "ned-livestats:parser-info" {
              tailf:meta-value "{'show':'show l2route evpn mac all | xml','template':'show-l2route-evpn.xsl'}";
            }
            key "topo-id";
            leaf topo-id {
              type string;
            }
            leaf mac-addr {
              type string;
            }
            leaf prod-type {
              type string;
            }
            leaf next-hop {
              type string;
            }
          }
        }
        container mac-ip {
          tailf:info
            "MAC-IP route";
          list all {
            tailf:meta-data "ned-livestats:parser-info" {
              tailf:meta-value "{'show':'show l2route evpn mac-ip all | xml','template':'show-l2route-evpn.xsl'}";
            }
            key "topo-id";
            leaf topo-id {
              type string;
            }
            leaf mac-addr {
              type string;
            }
            leaf prod-type {
              type string;
            }
            leaf host-ip {
              type string;
            }
            leaf next-hop {
              type string;
            }
          }
        }
      }
    }
    container cdp {
      tailf:ncs-device-type "cli-ned";
      tailf:display-when "not(../../ncs:module) or ../../ncs:module[ncs:name='tailf-ned-cisco-nx-stats'] or (../../ncs:live-status-protocol[not(ncs:capability)]) or (../../ncs:live-status-protocol/ncs:capability/ncs:module[.='tailf-ned-cisco-nx-stats'])";
      tailf:info
        "Show information about cdp";
      list neighbors {
        tailf:meta-data "ned-livestats:parser-info" {
          tailf:meta-value "{'show':'show cdp neighbors | xml','template':'show-cdp-neighbors.xsl'}";
        }
        key "intf-id";
        leaf intf-id {
          type string;
        }
        leaf ifindex {
          type uint32;
        }
        leaf device-id {
          type string;
        }
        leaf ttl {
          type uint32;
        }
        leaf-list capability {
          type string;
        }
        leaf platform-id {
          type string;
        }
        leaf port-id {
          type string;
        }
      }
    }
    container lldp {
      tailf:ncs-device-type "cli-ned";
      tailf:display-when "not(../../ncs:module) or ../../ncs:module[ncs:name='tailf-ned-cisco-nx-stats'] or (../../ncs:live-status-protocol[not(ncs:capability)]) or (../../ncs:live-status-protocol/ncs:capability/ncs:module[.='tailf-ned-cisco-nx-stats'])";
      tailf:info
        "Show information about lldp";
      list neighbors {
        tailf:meta-data "ned-livestats:parser-info" {
          tailf:meta-value "{'show':'show lldp neighbors detail | xml','template':'show-lldp-neighbors.xsl'}";
        }
        key "chassis-id port-id";
        tailf:info
          "Show lldp neighbor information";
        leaf chassis-id {
          type string;
        }
        leaf port-id {
          type string;
        }
        leaf chassis-type {
          type string;
        }
        leaf port-type {
          type string;
        }
        leaf local-port-id {
          type string;
        }
        leaf port-desc {
          type string;
        }
        leaf system-name {
          type string;
        }
        leaf system-desc {
          type string;
        }
        leaf time-remaining {
          type string;
        }
        leaf system-capability {
          type string;
        }
        leaf enabled-capability {
          type string;
        }
        leaf mgmt-addr {
          type string;
        }
        leaf mgmt-addr-type {
          type string;
        }
        leaf mgmt-addr-ipv6 {
          type string;
        }
        leaf mgmt-addr-ipv6-type {
          type string;
        }
        leaf vlan-id {
          type string;
        }
        leaf invalid-vlan-id {
          type string;
        }
        leaf ttl {
          type string;
        }
      }
    }
    container bgp {
      tailf:ncs-device-type "cli-ned";
      tailf:display-when "not(../../ncs:module) or ../../ncs:module[ncs:name='tailf-ned-cisco-nx-stats'] or (../../ncs:live-status-protocol[not(ncs:capability)]) or (../../ncs:live-status-protocol/ncs:capability/ncs:module[.='tailf-ned-cisco-nx-stats'])";
      tailf:info
        "Display BGP status and configuration";
      container event-history {
        list events {
          tailf:meta-data "ned-livestats:parser-info" {
            tailf:meta-value "{'show':'show bgp event-history events','template':'show_bgp_event-history_events.textfsm'}";
          }
          // NCS drop tailf:cli-enforce-table
          ordered-by user;
          key "timestamp";
          leaf timestamp {
            type string;
          }
          leaf event {
            type string;
          }
        }
      }
      container internal {
        tailf:info
          "Show internal information";
        container evi {
          tailf:info
            "Display information about EVI database";
          tailf:meta-data "ned-livestats:parser-info" {
            tailf:meta-value "{'show':'show bgp internal evi | xml','template':'show-bgp-internal-evi.xsl'}";
          }
          leaf l2ribbound {
            type string;
          }
          leaf l2ribvnireqs {
            type string;
          }
          leaf l2ribvniadds {
            type string;
          }
          leaf l2ribvnidels {
            type string;
          }
          leaf evpnisup {
            type string;
          }
          leaf evpnregistered {
            type string;
          }
          leaf evpndowninprogress {
            type string;
          }
          leaf evpnupdeferred {
            type string;
          }
          leaf evpnregistercount {
            type string;
          }
          leaf evpnregisterfail {
            type string;
          }
          leaf evpnderegistercount {
            type string;
          }
          leaf evpnderegisterfail {
            type string;
          }
          leaf evpnflowcontrol {
            type string;
          }
          leaf evpnflowcontrolenabled {
            type string;
          }
          leaf evpnflowcontroldisabled {
            type string;
          }
          list rdinfo {
            key "rdinford";
            leaf rdinford {
              type string;
            }
            leaf rdinfol3vni {
              type string;
            }
            leaf rdinfoeviid {
              type string;
            }
            leaf rdinfoname {
              type string;
            }
            leaf rdinfonrprefixeslocal {
              type string;
            }
            leaf rdinfonrprefixesbrib {
              type string;
            }
            leaf rdinfonrexplocall3vpnpaths {
              type string;
            }
            leaf rdinfonrimpremotel3vpnpaths {
              type string;
            }
          }
          list ctx {
            key "ctxeviid";
            leaf ctxeviid {
              type string;
            }
            leaf ctxl3vni {
              type string;
            }
            leaf ctxeviname {
              type string;
            }
            leaf ctxenabled {
              type string;
            }
            leaf ctxdeletepending {
              type string;
            }
            leaf ctxstale {
              type string;
            }
            leaf ctximportpending {
              type string;
            }
            leaf ctximportinprogress {
              type string;
            }
            leaf ctxencap {
              type string;
            }
            leaf ctxtopoid {
              type string;
            }
            leaf ctxethtagid {
              type string;
            }
            leaf ctxvnicount {
              type string;
            }
            leaf ctxpcifindx {
              type string;
            }
            leaf ctxvtepip {
              type string;
            }
            leaf ctxvtepvpcip {
              type string;
            }
            leaf ctxvtepvipr {
              type string;
            }
            leaf ctxactiveexportrtcount {
              type string;
            }
            leaf ctxcfgexportrtcount {
              type string;
            }
            leaf ctxexportrtchanges {
              type string;
            }
            leaf ctxexportrtchangespending {
              type string;
            }
            leaf ctxactiveimportrtcount {
              type string;
            }
            leaf ctxactiveimportrtlist {
              type string;
            }
            leaf ctxcfgimportrtcount {
              type string;
            }
            list ctxcfgimportrts {
              key "ctxcfgimportrt";
              leaf ctxcfgimportrt {
                type string;
              }
            }
            leaf ctximportrtchanges {
              type string;
            }
            leaf ctximportrtchangespending {
              type string;
            }
            leaf ctximetadd {
              type string;
            }
            leaf ctximetdel {
              type string;
            }
            leaf ctxsmetadd {
              type string;
            }
            leaf ctxsmetdel {
              type string;
            }
            leaf ctxmacadd {
              type string;
            }
            leaf ctxmacdel {
              type string;
            }
            leaf ctxmacipadd {
              type string;
            }
            leaf ctxmacipdel {
              type string;
            }
            leaf ctximetdnld {
              type string;
            }
            leaf ctximetwdraw {
              type string;
            }
            leaf ctxsmetdnld {
              type string;
            }
            leaf ctxsmetwdraw {
              type string;
            }
            leaf ctxmacdnld {
              type string;
            }
            leaf ctxmacwdraw {
              type string;
            }
            leaf ctxmacipdnld {
              type string;
            }
            leaf ctxmacipwdraw {
              type string;
            }
            leaf ctxeadevidnld {
              type string;
            }
            leaf ctxeadeviwdraw {
              type string;
            }
          }
        }
      }
      container l2vpn {
        tailf:info
          "Display BGP information for L2VPN address family";
        container evpn {
          tailf:info
            "Display BGP information for L2VPN EVPN address family";
          list neighbors {
            tailf:meta-data "ned-livestats:parser-info" {
              tailf:meta-value "{'show':'show bgp l2vpn evpn neighbors | xml','template':'show-bgp-l2vpn-evpn-neighbors.xsl'}";
            }
            tailf:info
              "Display all configured BGP neighbors";
            key "neighbor";
            leaf neighbor {
              type string;
            }
            leaf remoteas {
              type string;
            }
            leaf localas {
              type string;
            }
            leaf link {
              type string;
            }
            leaf index {
              type string;
            }
            leaf version {
              type string;
            }
            leaf remote-id {
              type string;
            }
            leaf state {
              type string;
            }
            leaf up {
              type string;
            }
            leaf elapsedtime {
              type string;
            }
            leaf restarttime {
              type string;
            }
            leaf sourceif {
              type string;
            }
            leaf remove-privateas {
              type string;
            }
            leaf lastread {
              type string;
            }
            leaf holdtime {
              type string;
            }
            leaf keepalivetime {
              type string;
            }
            leaf lastwrite {
              type string;
            }
            leaf msgrecvd {
              type string;
            }
            leaf notificationsrcvd {
              type string;
            }
            leaf recvbufbytes {
              type string;
            }
            leaf msgsent {
              type string;
            }
            leaf notificationssent {
              type string;
            }
            leaf sentbytesoutstanding {
              type string;
            }
            leaf connsestablished {
              type string;
            }
            leaf connsdropped {
              type string;
            }
            leaf connattempts {
              type string;
            }
            leaf resettime {
              type string;
            }
            leaf resetreason {
              type string;
            }
            leaf peerresettime {
              type string;
            }
            leaf peerresetreason {
              type string;
            }
            leaf epe {
              type string;
            }
            leaf firstkeepalive {
              type string;
            }
            leaf openssent {
              type string;
            }
            leaf opensrecvd {
              type string;
            }
            leaf notifssent {
              type string;
            }
            leaf notifsrecvd {
              type string;
            }
            leaf updatessent {
              type string;
            }
            leaf updatesrecvd {
              type string;
            }
            leaf keepalivesent {
              type string;
            }
            leaf keepaliverecvd {
              type string;
            }
            leaf rtrefreshsent {
              type string;
            }
            leaf rtrefreshrecvd {
              type string;
            }
            leaf capabilitiessent {
              type string;
            }
            leaf capabilitiesrecvd {
              type string;
            }
            leaf bytessent {
              type string;
            }
            leaf bytesrecvd {
              type string;
            }
            leaf capgradvertised {
              type string;
            }
            leaf capgrrecvd {
              type string;
            }
            leaf grrestarttime {
              type string;
            }
            leaf grstaletime {
              type string;
            }
            leaf grrecvdrestarttime {
              type string;
            }
            leaf capextendednhadvertised {
              type string;
            }
            leaf capextendednhrecvd {
              type string;
            }
            leaf localaddr {
              type string;
            }
            leaf localport {
              type string;
            }
            leaf remoteaddr {
              type string;
            }
            leaf remoteport {
              type string;
            }
            leaf fd {
              type string;
            }
            list peraf {
              key "per-afi";
              leaf per-afi {
                type string;
              }
              list persaf {
                key "per-safi";
                leaf per-safi {
                  type string;
                }
                leaf per-af-name {
                  type string;
                }
                leaf tableversion {
                  type string;
                }
                leaf neighbortableversion {
                  type string;
                }
                leaf pfxrecvd {
                  type string;
                }
                leaf pfxbytes {
                  type string;
                }
                leaf pfxsent {
                  type string;
                }
                leaf srpermitted {
                  type string;
                }
                leaf insoftreconfigallowed {
                  type string;
                }
                leaf sendcommunity {
                  type string;
                }
                leaf sendextcommunity {
                  type string;
                }
                leaf thirdpartynexthop {
                  type string;
                }
                leaf rrconfigured {
                  type string;
                }
                leaf asoverride {
                  type string;
                }
                leaf peerascheckdisabled {
                  type string;
                }
                list inpolicy {
                  key "nr";
                  leaf nr {
                    type string;
                  }
                  leaf type {
                    type string;
                  }
                  leaf name {
                    type string;
                  }
                  leaf handle {
                    type string;
                  }
                }
                list outpolicy {
                  key "nr";
                  leaf nr {
                    type string;
                  }
                  leaf type {
                    type string;
                  }
                  leaf name {
                    type string;
                  }
                  leaf handle {
                    type string;
                  }
                }
              }
            }
            list af {
              key "af-afi";
              leaf af-afi {
                type string;
              }
              list saf {
                key "af-safi";
                leaf af-safi {
                  type string;
                }
                leaf af-advertised {
                  type string;
                }
                leaf af-recvd {
                  type string;
                }
                leaf af-name {
                  type string;
                }
              }
            }
            list graf {
              key "gr-afi";
              leaf gr-afi {
                type string;
              }
              list grsaf {
                leaf gr-safi {
                  type string;
                }
                leaf gr-af-name {
                  type string;
                }
                leaf gr-adv {
                  type string;
                }
                leaf gr-recv {
                  type string;
                }
                leaf gr-fwd {
                  type string;
                }
              }
            }
            list capextendednhaf {
              key "capextendednh-afi";
              leaf capextendednh-afi {
                type string;
              }
              list capextendednhsaf {
                key "capextendednh-safi";
                leaf capextendednh-safi {
                  type string;
                }
                leaf capextendednh-af-name {
                  type string;
                }
              }
            }
          }
          container summary {
            list vrf {
              tailf:meta-data "ned-livestats:parser-info" {
                tailf:meta-value "{'show':'show bgp l2vpn evpn summary | xml','template':'show-bgp-l2vpn-evpn-summary.xsl'}";
              }
              key "vrf-name-out";
              leaf vrf-name-out {
                type string;
              }
              leaf vrf-router-id {
                type string;
              }
              leaf vrf-local-as {
                type string;
              }
              list af {
                key "af-id";
                leaf af-id {
                  type string;
                }
                list saf {
                  key "safi";
                  leaf safi {
                    type string;
                  }
                  leaf af-name {
                    type string;
                  }
                  leaf tableversion {
                    type string;
                  }
                  leaf configuredpeers {
                    type string;
                  }
                  leaf capablepeers {
                    type string;
                  }
                  leaf totalnetworks {
                    type string;
                  }
                  leaf totalpaths {
                    type string;
                  }
                  leaf memoryused {
                    type string;
                  }
                  leaf numberattrs {
                    type string;
                  }
                  leaf bytesattrs {
                    type string;
                  }
                  leaf numberpaths {
                    type string;
                  }
                  leaf bytespaths {
                    type string;
                  }
                  leaf numbercommunities {
                    type string;
                  }
                  leaf bytescommunities {
                    type string;
                  }
                  leaf numberclusterlist {
                    type string;
                  }
                  leaf bytesclusterlist {
                    type string;
                  }
                  leaf dampening {
                    type string;
                  }
                  list neighbor {
                    key "neighborid";
                    leaf neighborid {
                      type string;
                    }
                    leaf neighborversion {
                      type string;
                    }
                    leaf neighboras {
                      type string;
                    }
                    leaf msgrecvd {
                      type string;
                    }
                    leaf msgsent {
                      type string;
                    }
                    leaf neighbortableversion {
                      type string;
                    }
                    leaf inq {
                      type string;
                    }
                    leaf outq {
                      type string;
                    }
                    leaf time {
                      type string;
                    }
                    leaf state {
                      type string;
                    }
                    leaf prefixreceived {
                      type string;
                    }
                  }
                }
              }
            }
          }
          list vrf {
            tailf:meta-data "ned-livestats:parser-info" {
              tailf:meta-value "{'show':'show bgp l2vpn evpn | xml','template':'show-bgp-l2vpn-evpn.xsl'}";
            }
            key "vrf-name-out";
            leaf vrf-name-out {
              type string;
            }
            list afi {
              key "afi";
              leaf afi {
                type string;
              }
              list safi {
                key "safi";
                leaf safi {
                  type string;
                }
                leaf af-name {
                  type string;
                }
                leaf table-version {
                  type string;
                }
                leaf router-id {
                  type string;
                }
                list rd {
                  key "rd_val";
                  leaf rd_val {
                    type string;
                  }
                  leaf rd_vrf {
                    type string;
                  }
                  leaf rd_vniid {
                    type string;
                  }
                  list prefix {
                    key "nonipprefix";
                    leaf nonipprefix {
                      type string;
                    }
                    list path {
                      key "pathnr";
                      leaf pathnr {
                        type string;
                      }
                      leaf status {
                        type string;
                      }
                      leaf best {
                        type string;
                      }
                      leaf type {
                        type string;
                      }
                      leaf ipnexthop {
                        type string;
                      }
                      leaf metric {
                        type string;
                      }
                      leaf localpref {
                        type string;
                      }
                      leaf weight {
                        type string;
                      }
                      leaf aspath {
                        type string;
                      }
                      leaf origin {
                        type string;
                      }
                    }
                  }
                }
              }
            }
          }
        }
      }
    }
    container forwarding {
      tailf:ncs-device-type "cli-ned";
      tailf:display-when "not(../../ncs:module) or ../../ncs:module[ncs:name='tailf-ned-cisco-nx-stats'] or (../../ncs:live-status-protocol[not(ncs:capability)]) or (../../ncs:live-status-protocol/ncs:capability/ncs:module[.='tailf-ned-cisco-nx-stats'])";
      list vrf {
        tailf:meta-data "ned-livestats:parser-info" {
          tailf:meta-value "{'show':'show vrf | xml','template':'show-vrf.xsl'}";
        }
        key "name";
        leaf name {
          type string;
        }
        leaf id {
          type string;
        }
        leaf state {
          type string;
        }
        leaf reason {
          type string;
        }
        container ipv4 {
          tailf:meta-data "ned-livestats:parser-info" {
            tailf:meta-value "{'show':'show forwarding vrf %s ipv4 route | xml','template':'show-forwarding-vrf-ipv4-route.xsl'}";
          }
          list route {
            key "prefix";
            leaf prefix {
              type string;
            }
            list path {
              key "nexthop";
              leaf nexthop {
                type string;
              }
              leaf ifname {
                type string;
              }
              leaf labels {
                type string;
              }
            }
          }
        }
      }
    }
    container interface {
      tailf:ncs-device-type "cli-ned";
      tailf:display-when "not(../../ncs:module) or ../../ncs:module[ncs:name='tailf-ned-cisco-nx-stats'] or (../../ncs:live-status-protocol[not(ncs:capability)]) or (../../ncs:live-status-protocol/ncs:capability/ncs:module[.='tailf-ned-cisco-nx-stats'])";

      grouping eth-children {
        leaf name {
          type string;
        }
        leaf state {
          type string;
        }
        leaf desc {
          type string;
        }
        leaf admin-state {
          type string;
        }
        leaf share-state {
          type string;
        }
        leaf hw-desc {
          type string;
        }
        leaf hw-addr {
          type string;
        }
        leaf bia-addr {
          type string;
        }
        leaf mtu {
          type string;
        }
        leaf bw {
          type string;
        }
        leaf dly {
          type string;
        }
        leaf reliability {
          type string;
        }
        leaf txload {
          type string;
        }
        leaf rxload {
          type string;
        }
        leaf medium {
          type string;
        }
        leaf mode {
          type string;
        }
        leaf duplex {
          type string;
        }
        leaf speed {
          type string;
        }
        leaf media {
          type string;
        }
        leaf beacon {
          type string;
        }
        leaf autoneg {
          type string;
        }
        leaf in-flowctrl {
          type string;
        }
        leaf out-flowctrl {
          type string;
        }
        leaf mdix {
          type string;
        }
        leaf ratemode {
          type string;
        }
        leaf swt-monitor {
          type string;
        }
        leaf ethertype {
          type string;
        }
        leaf eee-state {
          type string;
        }
        leaf link-flapped {
          type string;
        }
        leaf clear-counters {
          type string;
        }
        leaf reset-cntr {
          type string;
        }
        leaf load-interval1-rx {
          type string;
        }
        leaf load-interval1-tx {
          type string;
        }
        leaf inrate1-bits {
          type string;
        }
        leaf inrate1-pkts {
          type string;
        }
        leaf outrate1-bits {
          type string;
        }
        leaf outrate1-pkts {
          type string;
        }
        leaf inucast {
          type string;
        }
        leaf inbcast {
          type string;
        }
        leaf inmcast {
          type string;
        }
        leaf inpkts {
          type string;
        }
        leaf jumbo-inpkts {
          type string;
        }
        leaf inbytes {
          type string;
        }
        leaf inpause {
          type string;
        }
        leaf indiscard {
          type string;
        }
        leaf inerr {
          type string;
        }
        leaf outucast {
          type string;
        }
        leaf outbcast {
          type string;
        }
        leaf outmcast {
          type string;
        }
        leaf outpkts {
          type string;
        }
        leaf jumbo-outpkts {
          type string;
        }
        leaf outbytes {
          type string;
        }
        leaf outpause {
          type string;
        }
        leaf outdiscard {
          type string;
        }
        leaf outerr {
          type string;
        }
        leaf storm-supp {
          type string;
        }
        leaf runts {
          type string;
        }
        leaf giants {
          type string;
        }
        leaf crc {
          type string;
        }
        leaf nobuf {
          type string;
        }
        leaf frame {
          type string;
        }
        leaf overrun {
          type string;
        }
        leaf underrun {
          type string;
        }
        leaf ignored {
          type string;
        }
        leaf watchdog {
          type string;
        }
        leaf bad-eth {
          type string;
        }
        leaf bad-proto {
          type string;
        }
        leaf in-ifdown-drops {
          type string;
        }
        leaf dribble {
          type string;
        }
        leaf coll {
          type string;
        }
        leaf deferred {
          type string;
        }
        leaf latecoll {
          type string;
        }
        leaf lostcarrier {
          type string;
        }
        leaf nocarrier {
          type string;
        }
        leaf babbles {
          type string;
        }
      }
      list ethernet {
        tailf:meta-data "ned-livestats:parser-info" {
          tailf:meta-value "{'show':{'cdb':'nx:interface/Ethernet','node':['name']},'recursive':false,'template':'show-interface-ethernet.xsl', 'show-entry':{'cmd':'show interface ethernet %s | xml','template':'show-interface-ethernet-entry.xsl'}}";
        }
        key "name";
        uses eth-children;
      }
      list port-channel {
        tailf:meta-data "ned-livestats:parser-info" {
          tailf:meta-value "{'show':{'cdb':'nx:interface/port-channel','node':['name']},'recursive':false,'template':'show-interface-ethernet.xsl', 'show-entry':{'cmd':'show interface port-channel %s | xml','template':'show-interface-ethernet-entry.xsl'}}";
        }
        key "name";
        uses eth-children;
      }
      list vlan {
        tailf:meta-data "ned-livestats:parser-info" {
          tailf:meta-value "{'show':{'cdb':'nx:interface/Vlan','node':['name']},'recursive':false,'template':'show-interface-vlan.xsl', 'show-entry':{'cmd':'show interface vlan %s | xml','template':'show-interface-vlan-entry.xsl'}}";
        }
        key "name";
        leaf name {
          type string;
        }
        leaf admin-state {
          type string;
        }
        leaf rsn-desc {
          type string;
        }
        leaf line-proto {
          type string;
        }
        leaf mac {
          type string;
        }
        leaf mtu {
          type string;
        }
        leaf bw {
          type string;
        }
        leaf delay {
          type string;
        }
        leaf type {
          type string;
        }
        leaf tx-load {
          type string;
        }
        leaf rx-load {
          type string;
        }
        leaf arp-type {
          type string;
        }
        leaf time-last-cleared {
          type string;
        }
        leaf load-interval1-rx {
          type string;
        }
        leaf load-interval1-tx {
          type string;
        }
        leaf inrate1-bits {
          type string;
        }
        leaf inrate1-pkts {
          type string;
        }
        leaf outrate1-bits {
          type string;
        }
        leaf outrate1-pkts {
          type string;
        }
        leaf routed-pkts-in {
          type string;
        }
        leaf routed-bytes-in {
          type string;
        }
        leaf routed-pkts-out {
          type string;
        }
        leaf routed-bytes-out {
          type string;
        }
        leaf ucast-bytes-in {
          type string;
        }
        leaf ucast-pkts-in {
          type string;
        }
        leaf mcast-bytes-in {
          type string;
        }
        leaf mcast-pkts-in {
          type string;
        }
        leaf bcast-bytes-in {
          type string;
        }
        leaf bcast-pkts-in {
          type string;
        }
        leaf ucast-bytes-out {
          type string;
        }
        leaf ucast-pkts-out {
          type string;
        }
        leaf mcast-bytes-out {
          type string;
        }
        leaf mcast-pkts-out {
          type string;
        }
      }
    }
    container ip {
      tailf:ncs-device-type "cli-ned";
      tailf:display-when "not(../../ncs:module) or ../../ncs:module[ncs:name='tailf-ned-cisco-nx-stats'] or (../../ncs:live-status-protocol[not(ncs:capability)]) or (../../ncs:live-status-protocol/ncs:capability/ncs:module[.='tailf-ned-cisco-nx-stats'])";
      container route {
        list vrf {
          tailf:meta-data "ned-livestats:parser-info" {
            tailf:meta-value "{'show':'show ip route vrf all | xml','template':'show-ip-route-vrf-all.xsl'}";
          }
          key "name";
          leaf name {
            type string;
          }
          list prefix {
            key "ipprefix";
            leaf ipprefix {
              type string;
            }
            leaf ucast-nhops {
              type string;
            }
            leaf mcast-nhops {
              type string;
            }
            leaf attached {
              type string;
            }
            list path {
              key "ipnexthop";
              leaf ipnexthop {
                type string;
              }
              leaf uptime {
                type string;
              }
              leaf ifname {
                type string;
              }
              leaf pref {
                type string;
              }
              leaf metric {
                type string;
              }
              leaf clientname {
                type string;
              }
              leaf ubest {
                type string;
              }
            }
          }
        }
      }
    }
    container vlan {
      tailf:ncs-device-type "cli-ned";
      tailf:display-when "not(../../ncs:module) or ../../ncs:module[ncs:name='tailf-ned-cisco-nx-stats'] or (../../ncs:live-status-protocol[not(ncs:capability)]) or (../../ncs:live-status-protocol/ncs:capability/ncs:module[.='tailf-ned-cisco-nx-stats'])";
      list vlans {
        tailf:meta-data "ned-livestats:parser-info" {
          tailf:meta-value "{'show':'show vlan | xml','template':'show-vlan.xsl'}";
        }
        key "vlanid";
        leaf vlanid {
          type string;
        }
        leaf vlanname {
          type string;
        }
        leaf vlanstate {
          type string;
        }
        leaf shutstate {
          type string;
        }
        leaf-list ports {
          ordered-by user;
          type string;
        }
        leaf media-type {
          type string;
        }
        leaf vlanmode {
          type string;
        }
      }
      list remote-span-vlans {
        key "primary";
        leaf primary {
          type string;
        }
        leaf secondary {
          type string;
        }
        leaf type {
          type string;
        }
        leaf ports {
          type string;
        }
      }
      list counters {
        tailf:meta-data "ned-livestats:parser-info" {
          tailf:meta-value "{'show':'show vlan counters | xml','template':'show-vlan-counters.xsl'}";
        }
        key "vlanid";
        tailf:info
          "Display counters";
        leaf vlanid {
          type string;
        }
        leaf ucast-bytes-in {
          type string;
        }
        leaf ucast-packets-in {
          type string;
        }
        leaf mcast-bytes-in {
          type string;
        }
        leaf mcast-packets-in {
          type string;
        }
        leaf bcast-bytes-in {
          type string;
        }
        leaf bcast-packets-in {
          type string;
        }
        leaf ucast-bytes-out {
          type string;
        }
        leaf ucast-packets-out {
          type string;
        }
        leaf l3-ucast-bytes-in {
          type string;
        }
        leaf l3-ucast-packets-in {
          type string;
        }
      }
    }
    container vpc {
      tailf:ncs-device-type "cli-ned";
      tailf:display-when "not(../../ncs:module) or ../../ncs:module[ncs:name='tailf-ned-cisco-nx-stats'] or (../../ncs:live-status-protocol[not(ncs:capability)]) or (../../ncs:live-status-protocol/ncs:capability/ncs:module[.='tailf-ned-cisco-nx-stats'])";
      container brief {
        tailf:meta-data "ned-livestats:parser-info" {
          tailf:meta-value "{'show':'show vpc brief | xml','template':'show-vpc-brief.xsl'}";
        }
        leaf vpc-domain-id {
          type string;
        }
        leaf vpc-peer-status {
          type string;
        }
        leaf vpc-peer-status-reason {
          type string;
        }
        leaf vpc-peer-keepalive-status {
          type string;
        }
        leaf vpc-peer-consistency {
          type string;
        }
        leaf vpc-per-vlan-peer-consistency {
          type string;
        }
        leaf vpc-peer-consistency-status {
          type string;
        }
        leaf vpc-type-2-consistency {
          type string;
        }
        leaf vpc-type-2-consistency-status {
          type string;
        }
        leaf vpc-role {
          type string;
        }
        leaf num-of-vpcs {
          type string;
        }
        leaf peer-gateway {
          type string;
        }
        leaf dual-active-excluded-vlans {
          type string;
        }
        leaf vpc-graceful-consistency-check-status {
          type string;
        }
        leaf vpc-auto-recovery-status {
          type string;
        }
        leaf vpc-delay-restore-status {
          type string;
        }
        leaf vpc-delay-restore-svi-status {
          type string;
        }
        leaf operational-l3-peer {
          type string;
        }
        leaf vpc-peer-link-hdr {
          type string;
        }
        list peerlink {
          key "peer-link-id";
          leaf peer-link-id {
            type uint32;
          }
          leaf peerlink-ifindex {
            type string;
          }
          leaf peer-link-port-state {
            type string;
          }
          leaf peer-up-vlan-bitset {
            type string;
          }
        }
        list vpc-list {
          key "vpc-id";
          leaf vpc-id {
            type uint32;
          }
          leaf vpc-ifindex {
            type string;
          }
          leaf vpc-port-state {
            type string;
          }
          leaf phy-port-if-removed {
            type string;
          }
          leaf vpc-thru-peerlink {
            type string;
          }
          leaf vpc-consistency {
            tailf:code-name "brief-vpc-consistency";
            type string;
          }
          leaf vpc-consistency-status {
            type string;
          }
          leaf up-vlan-bitset {
            type string;
          }
          leaf es-attr {
            type string;
          }
        }
      }
      container role {
        tailf:meta-data "ned-livestats:parser-info" {
          tailf:meta-value "{'show':'show vpc role | xml','template':'show-vpc-role.xsl'}";
        }
        leaf vpc-peer-status {
          type string;
        }
        leaf vpc-peer-status-reason {
          type string;
        }
        leaf vpc-current-role {
          type string;
        }
        leaf dual-active-detected {
          type string;
        }
        leaf vpc-system-mac {
          type string;
        }
        leaf vpc-system-prio {
          type string;
        }
        leaf vpc-local-system-mac {
          type string;
        }
        leaf vpc-local-system-prio {
          type string;
        }
        leaf vpc-local-role-prio {
          type string;
        }
        leaf vpc-peer-system-mac {
          type string;
        }
        leaf vpc-peer-system-prio {
          type string;
        }
        leaf vpc-peer-role-prio {
          type string;
        }
      }
      container peer-keepalive {
        tailf:meta-data "ned-livestats:parser-info" {
          tailf:meta-value "{'show':'show vpc peer-keepalive | xml','template':'show-vpc-peer-keepalive.xsl'}";
        }
        leaf vpc-peer-keepalive-status {
          type string;
        }
        leaf vpc-keepalive-dest {
          type string;
        }
        leaf vpc-keepalive-send-interface {
          type string;
        }
        leaf vpc-keepalive-receive-interface {
          type string;
        }
        leaf vpc-keepalive-send-tstamp {
          type string;
        }
        leaf vpc-keepalive-receive-tstamp {
          type string;
        }
        leaf vpc-peer-keepalive-up-time {
          type string;
        }
        leaf vpc-keepalive-send-status {
          type string;
        }
        leaf vpc-keepalive-receive-status {
          type string;
        }
        leaf vpc-keepalive-lastupdate {
          type string;
        }
        leaf vpc-keepalive-interval {
          type string;
        }
        leaf vpc-keepalive-timeout {
          type string;
        }
        leaf vpc-keepalive-hold-timeout {
          type string;
        }
        leaf vpc-keepalive-vrf {
          type string;
        }
        leaf vpc-keepalive-udp-port {
          type string;
        }
        leaf vpc-keepalive-tos {
          type string;
        }
      }
      container consistency-parameters {
        container global {
          tailf:meta-data "ned-livestats:parser-info" {
            tailf:meta-value "{'show':'show vpc consistency-parameters global | xml','template':'show-vpc-consistency-parameters-global.xsl'}";
          }
          list vpc_consistency {
            key "vpc-param-name";
            leaf vpc-param-name {
              type string;
            }
            leaf vpc-param-type {
              type string;
            }
            leaf vpc-param-local-val {
              type string;
            }
            leaf vpc-param-peer-val {
              type string;
            }
          }
        }
      }
    }
    container port-channel {
      tailf:ncs-device-type "cli-ned";
      tailf:display-when "not(../../ncs:module) or ../../ncs:module[ncs:name='tailf-ned-cisco-nx-stats'] or (../../ncs:live-status-protocol[not(ncs:capability)]) or (../../ncs:live-status-protocol/ncs:capability/ncs:module[.='tailf-ned-cisco-nx-stats'])";
      container summary {
        list channel {
          tailf:meta-data "ned-livestats:parser-info" {
            tailf:meta-value "{'show':'show port-channel summary | xml','template':'show-port-channel-summary.xsl'}";
          }
          key "group";
          leaf group {
            type string;
          }
          leaf port-channel {
            type string;
          }
          leaf layer {
            type string;
          }
          leaf status {
            type string;
          }
          leaf type {
            type string;
          }
          leaf prtcl {
            type string;
          }
          list member {
            key "port";
            leaf port {
              type string;
            }
            leaf port-status {
              type string;
            }
          }
        }
      }
    }
    container vtp {
      tailf:ncs-device-type "cli-ned";
      tailf:display-when "not(../../ncs:module) or ../../ncs:module[ncs:name='tailf-ned-cisco-nx-stats'] or (../../ncs:live-status-protocol[not(ncs:capability)]) or (../../ncs:live-status-protocol/ncs:capability/ncs:module[.='tailf-ned-cisco-nx-stats'])";
      container status {
        tailf:meta-data "ned-livestats:parser-info" {
          tailf:meta-value "{'show':'show vtp status ; show vtp password','template':'show_vtp_status.textfsm'}";
        }
        leaf version-capable {
          type uint8;
        }
        leaf max-vlans {
          type uint16;
        }
        leaf existing-vlans {
          type uint16;
        }
        leaf operating-mode {
          type string;
        }
        leaf domain-name {
          type string;
        }
        leaf pruning-mode {
          type string;
        }
        leaf version-running {
          type uint8;
        }
        leaf interface {
          type string;
        }
        leaf password {
          type string;
        }
      }
    }
    container exec {
      tailf:ncs-device-type "cli-ned";
      tailf:display-when "not(../../ncs:module) or ../../ncs:module[ncs:name='tailf-ned-cisco-nx-stats'] or (../../ncs:live-status-protocol[not(ncs:capability)]) or (../../ncs:live-status-protocol/ncs:capability/ncs:module[.='tailf-ned-cisco-nx-stats'])";
      tailf:info
        "Execute commands on device";
      tailf:action show {
        tailf:actionpoint ncsproxy {
          tailf:internal;
        }
        tailf:info
          "Execute show commands";
        // NCS drop tailf:actionpoint
        input {
          leaf-list args {
            tailf:cli-drop-node-name;
            tailf:cli-flat-list-syntax;
            type string {
              tailf:info
                "show argument(s)";
            }
          }
        }
        output {
          leaf result {
            type string;
          }
        }
      }
      tailf:action copy {
        tailf:actionpoint ncsproxy {
          tailf:internal;
        }
        tailf:info
          "Copy from one file to another";
        // NCS drop tailf:actionpoint
        input {
          leaf-list args {
            tailf:cli-drop-node-name;
            tailf:cli-flat-list-syntax;
            type string {
              tailf:info
                "copy argument(s)";
            }
          }
        }
        output {
          leaf result {
            type string;
          }
        }
      }
      tailf:action ping {
        tailf:actionpoint ncsproxy {
          tailf:internal;
        }
        tailf:info
          "Test network reachability";
        // NCS drop tailf:actionpoint
        input {
          leaf-list args {
            tailf:cli-drop-node-name;
            tailf:cli-flat-list-syntax;
            type string {
              tailf:info
                "ping argument(s) (NOTE: will automatically use ping6 if ipv6 address used)";
            }
          }
        }
        output {
          leaf result {
            type string;
          }
        }
      }
      tailf:action traceroute {
        tailf:actionpoint ncsproxy {
          tailf:internal;
        }
        tailf:info
          "Traceroute to destination";
        // NCS drop tailf:actionpoint
        input {
          leaf-list args {
            tailf:cli-drop-node-name;
            tailf:cli-flat-list-syntax;
            type string {
              tailf:info
                "traceroute argument(s) (NOTE: will automatically use traceroute6 if ipv6 address used)";
            }
          }
        }
        output {
          leaf result {
            type string;
          }
        }
      }
      tailf:action any {
        tailf:actionpoint ncsproxy {
          tailf:internal;
        }
        tailf:info
          "Execute any command on device";
        // NCS drop tailf:actionpoint
        input {
          leaf-list args {
            tailf:cli-drop-node-name;
            tailf:cli-flat-list-syntax;
            type string {
              tailf:info
                "WORD;;any <cmd> [option(s)], e.g: any event manager run my_applet (see README for more info)";
            }
          }
        }
        output {
          leaf result {
            type string;
          }
        }
      }
      tailf:action any-hidden {
        tailf:actionpoint ncsproxy {
          tailf:internal;
        }
        tailf:info
          "Execute any command on device, command-line and answers will be hidden from log/trace";
        // NCS drop tailf:actionpoint
        input {
          leaf answers {
            tailf:suppress-echo true;
            type string {
              tailf:info
                "<answers>;;Comma-separated list of answers to prompts";
            }
          }
          leaf command-line {
            mandatory true;
            tailf:suppress-echo true;
            type string {
              tailf:info
                "LINE;;<cmd-line> NOTE: Whole line is given in a single string, i.e. quoted if needed";
            }
          }
        }
        output {
          leaf result {
            type string;
          }
        }
      }
      tailf:action internal {
        tailf:actionpoint ncsproxy {
          tailf:internal;
        }
        tailf:info
          "Execute internal (to ned) command";
        // NCS drop tailf:actionpoint
        input {
          leaf-list args {
            tailf:cli-drop-node-name;
            tailf:cli-flat-list-syntax;
            type string {
              tailf:info
                "WORD;;internal <cmd> [option(s)]";
            }
          }
        }
        output {
          leaf result {
            type string;
          }
        }
      }
    }
  }
}
